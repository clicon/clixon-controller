module clixon-controller {
    yang-version 1.1;
    namespace "urn:example:clixon-controller";
    prefix controller;
    import ietf-yang-types {
        prefix "yang";
    }
    import ietf-inet-types {
        prefix inet;
    }
    import ietf-yang-schema-mount {
        prefix yangmnt;
    }
    description
        "Clixon controller";
    revision 2023-01-01 {
        description "Initial version";
    }
    typedef connection-type{
        description
            "Which connection method to connect frm the controller to a device.
            ";
        type enumeration{
            enum NETCONF_SSH{
                description
                "NETCONF over SSH subsystem according to RFC 6242";
            }
        }
    }
    typedef connection-state{
        description
            "Device connection state. 
             The controller holds this connection state per device.";
        type enumeration{
            enum CLOSED {
                description
                "Not connected
                 Implicitly if no state exists for device, it is in CLOSED state";
            }
            enum CONNECTING {
                description
                "Connection initiated: connect called
                 Expect to receive netconf hello from device
                 Transient state that timeout to CLOSED.
                 Connect failures include (1) connect fails or (2) hello not received";
            }
            enum SCHEMA_LIST {
                description
                  "Get ietf-netconf-monitoring schema for all YANG schemas,
                  Waiting for reply
                  Transient state that timeout to CLOSED.";
            }
            enum SCHEMA_ONE {
                description
                "Get-schema sent to device for each yang the device announces
                 Waiting for reply
                 Transient state that timeout to CLOSED.";
            }
            enum DEVICE-SYNC {
                description
                    "Hello received and hello sent to device,
                     If device announces monitoring a get-state on ietf-netconf-monitoring
                     is sent.
                    Transient state that timeout to CLOSED.";
            }
            enum OPEN{
                description
                "Connection is open";
            }
            enum WRESP{
                description
                "Netconf reuest is sent, waiting for response.
                 Transient state that timeout to CLOSED.
                Currently not used, OBSOLETE?";
            }
        }
    }
    container services {
        description "Placeholder for services";
    }
    container generic{
        leaf device-timeout{
            description
                "Device transient state timeout in seconds";
            type uint32;
            default 60;
            units s;
        }
    }
    /* Generic config data */
    container devices{
        list device{
            key name;
            leaf name{
                type string;
            }
            leaf enable{
                type boolean;
                default true;
            }
            leaf description{
                description
                    "Description of node";
                type string;
            }
            leaf type{
                description
                    "Connection type, eg how to connect to (or from) the device";
                mandatory true;
                type connection-type;
            }
            leaf user{
                description
                    "Which use to connect as to the device, if applicable";
                type string;
            }
            leaf addr{
                description
                    "DNS name or ip address of device for connection setup (see also user)";
                type string;
            }
            leaf conn-state {
                description
                    "State of connection";
                config false;
                type connection-type;
                default CLOSED;
            }
            container capabilities {
                description
                    "May be duplicate if netconf-monitoring is implemented?";
                config false;
                leaf-list capability {
                    type string;
                    description
                        "List of NETCONF capabilities supported by the server.";
                }
            }
            leaf conn-state-timestamp {
                description "Timestamp of when entering current state";
                config false;
                type yang:date-and-time;
            }
            leaf sync-timestamp {
                description "Timestamp of last device synchronization";
                config false;
                type yang:date-and-time;
            }
            leaf logmsg {
                config false;
                type string;
            }
            //            container root{
            anydata root{
                description
                    "Mount-point for device configs";
                yangmnt:mount-point "root"{
                    description
                       "Root for yang models retrieved from device via get-schema";
                }
            }
        }
    }
    rpc sync {
        description "Read the config of one or several devices.";
        input {
            leaf name {
                description
                    "Name of device to connect to, can use wildchars for several.";
                type string;
            }
        }
        output {
            leaf-list name {
                description
                    "Names of devices where connections have been initiated.
                    Note the connection establishement is asynchronous and continues in background";
                type string;
            }
        }
    }
}
