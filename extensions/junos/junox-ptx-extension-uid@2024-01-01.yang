/*
 * Extension to ignore the UID configuration in the Junos
 * configuration since it can be generated by the system and will not
 * match the configuration.
 */

module controller-extensions-uid {
    namespace "http://clicon.org/ext/uid";

    prefix cl-ext;

    import clixon-lib {
        prefix cl;
    }

    import junos-conf-root {
	prefix jc;
    }

    import junos-conf-system {
	prefix jcs;
    }

    revision 2024-01-01 {
	description "Initial prototype";
    }

    augment "/jc:configuration/jcs:system/jcs:login/jcs:user/jcs:uid" {
	cl:ignore-compare;
    }
}
