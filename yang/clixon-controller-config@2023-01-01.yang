module clixon-controller-config {
    yang-version 1.1;
    namespace "http://clicon.org/controller-config";
    prefix ctrc;
    import clixon-config {
        prefix "cc";
    }
    description
        "Clixon controller config extending regular clixon-config";
    revision 2023-01-01 {
        description "Initial version";
    }
    augment "/cc:clixon-config" {
        description
            "Controller-specific options";
        leaf CONTROLLER_ACTION_COMMAND{
            description
                "Binary command and arguments of action server";
            type string;
            default "/usr/local/bin/clixon_server.py";
        }
        leaf CONTROLLER_PYAPI_MODULE_PATH{
            default "/usr/local/share/clixon/controller/modules/";
            type string;
        }
        leaf CONTROLLER_PYAPI_MODULE_FILTER{
            type string;
            default "";
        }
        leaf CONTROLLER_PYAPI_PIDFILE{
            type string;
            default "/tmp/clixon_pyapi.pid";
        }
    }
}
