module clixon-controller-config {
    yang-version 1.1;
    namespace "http://clicon.org/controller-config";
    prefix ctrc;
    import clixon-config {
        prefix "cc";
    }
    description
        "Clixon controller config extending regular clixon-config";
    revision 2025-05-01 {
        description
            "Released in 1.5.0";
    }
    revision 2025-02-01 {
        description
            "Added CONTROLLER_SSH_IDENTITYFILE
             Removed CONTROLLER_YANG_SCHEMA_MOUNT_DIR
             Released in 1.4.0";
    }
    revision 2024-08-01 {
        description
            "Moved default directories from clixon/controller to controller
             Removed defaults for CONTROLLER_ACTION_COMMAND, CONTROLLER_PYAPI_MODULE_PATH,
                                  and CONTROLLER_PYAPI_PIDFILE
             Obsoleted CONTROLLER_YANG_SCHEMA_MOUNT_DIR
             Released in 1.2.0";
    }
    revision 2023-11-01 {
        description
            "Added CONTROLLER_YANG_SCHEMA_MOUNT_DIR
             Released in 0.2.0";
    }
    revision 2023-01-01 {
        description "Initial version";
    }
    augment "/cc:clixon-config" {
        description
            "Controller-specific options";
        leaf CONTROLLER_ACTION_COMMAND{
            description
                "Binary command and arguments of action server";
            type string;
        }
        leaf CONTROLLER_PYAPI_MODULE_PATH{
            description
                "Directory where pyapi looks for python files.
                 Typically in /usr/local/share/controller/modules";
            type string;
        }
        leaf CONTROLLER_PYAPI_MODULE_FILTER{
            description
                "Comma separated list of services modules 
                 that should be ignored and not loaded.";
            type string;
        }
        leaf CONTROLLER_PYAPI_PIDFILE{
            description
                "Path to the pidfile for the controller. 
                 Typically /usr/local/var/run/controller/clixon_server.pid";
            type string;
        }
        leaf CONTROLLER_SSH_IDENTITYFILE{
            description
                "SSH Identityfile if not default";
            type string;
        }
    }
}
