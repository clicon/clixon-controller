module clixon-controller-config {
    yang-version 1.1;
    namespace "http://clicon.org/controller-config";
    prefix ctrc;
    import clixon-config {
        prefix "cc";
    }
    description
        "Clixon controller config extending regular clixon-config";
    revision 2023-11-01 {
        description
            "Added CONTROLLER_YANG_SCHEMA_MOUNT_DIR
             Released in 0.2.0";
    }
    revision 2023-01-01 {
        description "Initial version";
    }
    augment "/cc:clixon-config" {
        description
            "Controller-specific options";
        leaf CONTROLLER_ACTION_COMMAND{
            description
                "Binary command and arguments of action server";
            type string;
            default "/usr/local/bin/clixon_server.py";
        }
        leaf CONTROLLER_PYAPI_MODULE_PATH{
            default "/usr/local/share/clixon/controller/modules/";
            type string;
        }
        leaf CONTROLLER_PYAPI_MODULE_FILTER{
            type string;
            default "";
        }
        leaf CONTROLLER_PYAPI_PIDFILE{
            type string;
            default "/tmp/clixon_pyapi.pid";
        }
        leaf CONTROLLER_YANG_SCHEMA_MOUNT_DIR{
            description
                "Directory where device YANGs are stored locally.
                 This is both from RFC 6022 dynamic get-schema retrieval as well as
                 local module-set YANGs.
                 For get-schema, the controller looks in this dir before requesting the 
                 YANG from a device. If it exists there, it is loaded locally and not requested 
                 from the device.
                 For local (module-set) declared YANGs, the controller searches in this dir
                 for the YANG.
                 Thus the dir serves several purposes:
                  1. It serves as a cache for performance if multiple devices or restart of
                     the controller requests the same YANG.
                  2. A local YANG can override the YANG from a device for debugging or patch.
                  3. It serves as storage for locally defined YANGs.
                 NOTE: This dir must be accessible via the controllers YANG_DIR search part.";
            type string;
            default "/usr/local/share/clixon/controller/mounts";
        }
    }
}
